-- CHOICE with 256 or more root alternatives: the index is a constrained
-- whole number over 255, octet-aligned in the ALIGNED variant (X.691 23.6,
-- 11.5.7.2, 11.5.7.3). Checked against the references but not verified:
-- the proofs of a CHOICE this wide exceed the solver's limits (TODO.md).
-- tests/aper/run.sh: noverify
WideChoice DEFINITIONS AUTOMATIC TAGS ::= BEGIN
E300 ::= ENUMERATED { e0, e1, e2, e3, e4, e5, e6, e7, e8, e9, e10, e11, e12, e13, e14, e15, e16, e17, e18, e19, e20, e21, e22, e23, e24, e25, e26, e27, e28, e29, e30, e31, e32, e33, e34, e35, e36, e37, e38, e39, e40, e41, e42, e43, e44, e45, e46, e47, e48, e49, e50, e51, e52, e53, e54, e55, e56, e57, e58, e59, e60, e61, e62, e63, e64, e65, e66, e67, e68, e69, e70, e71, e72, e73, e74, e75, e76, e77, e78, e79, e80, e81, e82, e83, e84, e85, e86, e87, e88, e89, e90, e91, e92, e93, e94, e95, e96, e97, e98, e99, e100, e101, e102, e103, e104, e105, e106, e107, e108, e109, e110, e111, e112, e113, e114, e115, e116, e117, e118, e119, e120, e121, e122, e123, e124, e125, e126, e127, e128, e129, e130, e131, e132, e133, e134, e135, e136, e137, e138, e139, e140, e141, e142, e143, e144, e145, e146, e147, e148, e149, e150, e151, e152, e153, e154, e155, e156, e157, e158, e159, e160, e161, e162, e163, e164, e165, e166, e167, e168, e169, e170, e171, e172, e173, e174, e175, e176, e177, e178, e179, e180, e181, e182, e183, e184, e185, e186, e187, e188, e189, e190, e191, e192, e193, e194, e195, e196, e197, e198, e199, e200, e201, e202, e203, e204, e205, e206, e207, e208, e209, e210, e211, e212, e213, e214, e215, e216, e217, e218, e219, e220, e221, e222, e223, e224, e225, e226, e227, e228, e229, e230, e231, e232, e233, e234, e235, e236, e237, e238, e239, e240, e241, e242, e243, e244, e245, e246, e247, e248, e249, e250, e251, e252, e253, e254, e255, e256, e257, e258, e259, e260, e261, e262, e263, e264, e265, e266, e267, e268, e269, e270, e271, e272, e273, e274, e275, e276, e277, e278, e279, e280, e281, e282, e283, e284, e285, e286, e287, e288, e289, e290, e291, e292, e293, e294, e295, e296, e297, e298, e299 }
E256 ::= ENUMERATED { f0, f1, f2, f3, f4, f5, f6, f7, f8, f9, f10, f11, f12, f13, f14, f15, f16, f17, f18, f19, f20, f21, f22, f23, f24, f25, f26, f27, f28, f29, f30, f31, f32, f33, f34, f35, f36, f37, f38, f39, f40, f41, f42, f43, f44, f45, f46, f47, f48, f49, f50, f51, f52, f53, f54, f55, f56, f57, f58, f59, f60, f61, f62, f63, f64, f65, f66, f67, f68, f69, f70, f71, f72, f73, f74, f75, f76, f77, f78, f79, f80, f81, f82, f83, f84, f85, f86, f87, f88, f89, f90, f91, f92, f93, f94, f95, f96, f97, f98, f99, f100, f101, f102, f103, f104, f105, f106, f107, f108, f109, f110, f111, f112, f113, f114, f115, f116, f117, f118, f119, f120, f121, f122, f123, f124, f125, f126, f127, f128, f129, f130, f131, f132, f133, f134, f135, f136, f137, f138, f139, f140, f141, f142, f143, f144, f145, f146, f147, f148, f149, f150, f151, f152, f153, f154, f155, f156, f157, f158, f159, f160, f161, f162, f163, f164, f165, f166, f167, f168, f169, f170, f171, f172, f173, f174, f175, f176, f177, f178, f179, f180, f181, f182, f183, f184, f185, f186, f187, f188, f189, f190, f191, f192, f193, f194, f195, f196, f197, f198, f199, f200, f201, f202, f203, f204, f205, f206, f207, f208, f209, f210, f211, f212, f213, f214, f215, f216, f217, f218, f219, f220, f221, f222, f223, f224, f225, f226, f227, f228, f229, f230, f231, f232, f233, f234, f235, f236, f237, f238, f239, f240, f241, f242, f243, f244, f245, f246, f247, f248, f249, f250, f251, f252, f253, f254, f255 }
E300x ::= ENUMERATED { e0, e1, e2, e3, e4, e5, e6, e7, e8, e9, e10, e11, e12, e13, e14, e15, e16, e17, e18, e19, e20, e21, e22, e23, e24, e25, e26, e27, e28, e29, e30, e31, e32, e33, e34, e35, e36, e37, e38, e39, e40, e41, e42, e43, e44, e45, e46, e47, e48, e49, e50, e51, e52, e53, e54, e55, e56, e57, e58, e59, e60, e61, e62, e63, e64, e65, e66, e67, e68, e69, e70, e71, e72, e73, e74, e75, e76, e77, e78, e79, e80, e81, e82, e83, e84, e85, e86, e87, e88, e89, e90, e91, e92, e93, e94, e95, e96, e97, e98, e99, e100, e101, e102, e103, e104, e105, e106, e107, e108, e109, e110, e111, e112, e113, e114, e115, e116, e117, e118, e119, e120, e121, e122, e123, e124, e125, e126, e127, e128, e129, e130, e131, e132, e133, e134, e135, e136, e137, e138, e139, e140, e141, e142, e143, e144, e145, e146, e147, e148, e149, e150, e151, e152, e153, e154, e155, e156, e157, e158, e159, e160, e161, e162, e163, e164, e165, e166, e167, e168, e169, e170, e171, e172, e173, e174, e175, e176, e177, e178, e179, e180, e181, e182, e183, e184, e185, e186, e187, e188, e189, e190, e191, e192, e193, e194, e195, e196, e197, e198, e199, e200, e201, e202, e203, e204, e205, e206, e207, e208, e209, e210, e211, e212, e213, e214, e215, e216, e217, e218, e219, e220, e221, e222, e223, e224, e225, e226, e227, e228, e229, e230, e231, e232, e233, e234, e235, e236, e237, e238, e239, e240, e241, e242, e243, e244, e245, e246, e247, e248, e249, e250, e251, e252, e253, e254, e255, e256, e257, e258, e259, e260, e261, e262, e263, e264, e265, e266, e267, e268, e269, e270, e271, e272, e273, e274, e275, e276, e277, e278, e279, e280, e281, e282, e283, e284, e285, e286, e287, e288, e289, e290, e291, e292, e293, e294, e295, e296, e297, e298, e299, ..., x1, x2 }
C300 ::= CHOICE {
  a0 INTEGER (0..0),
  a1 BOOLEAN,
  a2 INTEGER (0..2),
  a3 BOOLEAN,
  a4 INTEGER (0..4),
  a5 BOOLEAN,
  a6 INTEGER (0..6),
  a7 BOOLEAN,
  a8 INTEGER (0..8),
  a9 BOOLEAN,
  a10 INTEGER (0..10),
  a11 BOOLEAN,
  a12 INTEGER (0..12),
  a13 BOOLEAN,
  a14 INTEGER (0..14),
  a15 BOOLEAN,
  a16 INTEGER (0..16),
  a17 BOOLEAN,
  a18 INTEGER (0..18),
  a19 BOOLEAN,
  a20 INTEGER (0..20),
  a21 BOOLEAN,
  a22 INTEGER (0..22),
  a23 BOOLEAN,
  a24 INTEGER (0..24),
  a25 BOOLEAN,
  a26 INTEGER (0..26),
  a27 BOOLEAN,
  a28 INTEGER (0..28),
  a29 BOOLEAN,
  a30 INTEGER (0..30),
  a31 BOOLEAN,
  a32 INTEGER (0..32),
  a33 BOOLEAN,
  a34 INTEGER (0..34),
  a35 BOOLEAN,
  a36 INTEGER (0..36),
  a37 BOOLEAN,
  a38 INTEGER (0..38),
  a39 BOOLEAN,
  a40 INTEGER (0..40),
  a41 BOOLEAN,
  a42 INTEGER (0..42),
  a43 BOOLEAN,
  a44 INTEGER (0..44),
  a45 BOOLEAN,
  a46 INTEGER (0..46),
  a47 BOOLEAN,
  a48 INTEGER (0..48),
  a49 BOOLEAN,
  a50 INTEGER (0..50),
  a51 BOOLEAN,
  a52 INTEGER (0..52),
  a53 BOOLEAN,
  a54 INTEGER (0..54),
  a55 BOOLEAN,
  a56 INTEGER (0..56),
  a57 BOOLEAN,
  a58 INTEGER (0..58),
  a59 BOOLEAN,
  a60 INTEGER (0..60),
  a61 BOOLEAN,
  a62 INTEGER (0..62),
  a63 BOOLEAN,
  a64 INTEGER (0..64),
  a65 BOOLEAN,
  a66 INTEGER (0..66),
  a67 BOOLEAN,
  a68 INTEGER (0..68),
  a69 BOOLEAN,
  a70 INTEGER (0..70),
  a71 BOOLEAN,
  a72 INTEGER (0..72),
  a73 BOOLEAN,
  a74 INTEGER (0..74),
  a75 BOOLEAN,
  a76 INTEGER (0..76),
  a77 BOOLEAN,
  a78 INTEGER (0..78),
  a79 BOOLEAN,
  a80 INTEGER (0..80),
  a81 BOOLEAN,
  a82 INTEGER (0..82),
  a83 BOOLEAN,
  a84 INTEGER (0..84),
  a85 BOOLEAN,
  a86 INTEGER (0..86),
  a87 BOOLEAN,
  a88 INTEGER (0..88),
  a89 BOOLEAN,
  a90 INTEGER (0..90),
  a91 BOOLEAN,
  a92 INTEGER (0..92),
  a93 BOOLEAN,
  a94 INTEGER (0..94),
  a95 BOOLEAN,
  a96 INTEGER (0..96),
  a97 BOOLEAN,
  a98 INTEGER (0..98),
  a99 BOOLEAN,
  a100 INTEGER (0..100),
  a101 BOOLEAN,
  a102 INTEGER (0..102),
  a103 BOOLEAN,
  a104 INTEGER (0..104),
  a105 BOOLEAN,
  a106 INTEGER (0..106),
  a107 BOOLEAN,
  a108 INTEGER (0..108),
  a109 BOOLEAN,
  a110 INTEGER (0..110),
  a111 BOOLEAN,
  a112 INTEGER (0..112),
  a113 BOOLEAN,
  a114 INTEGER (0..114),
  a115 BOOLEAN,
  a116 INTEGER (0..116),
  a117 BOOLEAN,
  a118 INTEGER (0..118),
  a119 BOOLEAN,
  a120 INTEGER (0..120),
  a121 BOOLEAN,
  a122 INTEGER (0..122),
  a123 BOOLEAN,
  a124 INTEGER (0..124),
  a125 BOOLEAN,
  a126 INTEGER (0..126),
  a127 BOOLEAN,
  a128 INTEGER (0..128),
  a129 BOOLEAN,
  a130 INTEGER (0..130),
  a131 BOOLEAN,
  a132 INTEGER (0..132),
  a133 BOOLEAN,
  a134 INTEGER (0..134),
  a135 BOOLEAN,
  a136 INTEGER (0..136),
  a137 BOOLEAN,
  a138 INTEGER (0..138),
  a139 BOOLEAN,
  a140 INTEGER (0..140),
  a141 BOOLEAN,
  a142 INTEGER (0..142),
  a143 BOOLEAN,
  a144 INTEGER (0..144),
  a145 BOOLEAN,
  a146 INTEGER (0..146),
  a147 BOOLEAN,
  a148 INTEGER (0..148),
  a149 BOOLEAN,
  a150 INTEGER (0..150),
  a151 BOOLEAN,
  a152 INTEGER (0..152),
  a153 BOOLEAN,
  a154 INTEGER (0..154),
  a155 BOOLEAN,
  a156 INTEGER (0..156),
  a157 BOOLEAN,
  a158 INTEGER (0..158),
  a159 BOOLEAN,
  a160 INTEGER (0..160),
  a161 BOOLEAN,
  a162 INTEGER (0..162),
  a163 BOOLEAN,
  a164 INTEGER (0..164),
  a165 BOOLEAN,
  a166 INTEGER (0..166),
  a167 BOOLEAN,
  a168 INTEGER (0..168),
  a169 BOOLEAN,
  a170 INTEGER (0..170),
  a171 BOOLEAN,
  a172 INTEGER (0..172),
  a173 BOOLEAN,
  a174 INTEGER (0..174),
  a175 BOOLEAN,
  a176 INTEGER (0..176),
  a177 BOOLEAN,
  a178 INTEGER (0..178),
  a179 BOOLEAN,
  a180 INTEGER (0..180),
  a181 BOOLEAN,
  a182 INTEGER (0..182),
  a183 BOOLEAN,
  a184 INTEGER (0..184),
  a185 BOOLEAN,
  a186 INTEGER (0..186),
  a187 BOOLEAN,
  a188 INTEGER (0..188),
  a189 BOOLEAN,
  a190 INTEGER (0..190),
  a191 BOOLEAN,
  a192 INTEGER (0..192),
  a193 BOOLEAN,
  a194 INTEGER (0..194),
  a195 BOOLEAN,
  a196 INTEGER (0..196),
  a197 BOOLEAN,
  a198 INTEGER (0..198),
  a199 BOOLEAN,
  a200 INTEGER (0..200),
  a201 BOOLEAN,
  a202 INTEGER (0..202),
  a203 BOOLEAN,
  a204 INTEGER (0..204),
  a205 BOOLEAN,
  a206 INTEGER (0..206),
  a207 BOOLEAN,
  a208 INTEGER (0..208),
  a209 BOOLEAN,
  a210 INTEGER (0..210),
  a211 BOOLEAN,
  a212 INTEGER (0..212),
  a213 BOOLEAN,
  a214 INTEGER (0..214),
  a215 BOOLEAN,
  a216 INTEGER (0..216),
  a217 BOOLEAN,
  a218 INTEGER (0..218),
  a219 BOOLEAN,
  a220 INTEGER (0..220),
  a221 BOOLEAN,
  a222 INTEGER (0..222),
  a223 BOOLEAN,
  a224 INTEGER (0..224),
  a225 BOOLEAN,
  a226 INTEGER (0..226),
  a227 BOOLEAN,
  a228 INTEGER (0..228),
  a229 BOOLEAN,
  a230 INTEGER (0..230),
  a231 BOOLEAN,
  a232 INTEGER (0..232),
  a233 BOOLEAN,
  a234 INTEGER (0..234),
  a235 BOOLEAN,
  a236 INTEGER (0..236),
  a237 BOOLEAN,
  a238 INTEGER (0..238),
  a239 BOOLEAN,
  a240 INTEGER (0..240),
  a241 BOOLEAN,
  a242 INTEGER (0..242),
  a243 BOOLEAN,
  a244 INTEGER (0..244),
  a245 BOOLEAN,
  a246 INTEGER (0..246),
  a247 BOOLEAN,
  a248 INTEGER (0..248),
  a249 BOOLEAN,
  a250 INTEGER (0..250),
  a251 BOOLEAN,
  a252 INTEGER (0..252),
  a253 BOOLEAN,
  a254 INTEGER (0..254),
  a255 BOOLEAN,
  a256 INTEGER (0..256),
  a257 BOOLEAN,
  a258 INTEGER (0..258),
  a259 BOOLEAN,
  a260 INTEGER (0..260),
  a261 BOOLEAN,
  a262 INTEGER (0..262),
  a263 BOOLEAN,
  a264 INTEGER (0..264),
  a265 BOOLEAN,
  a266 INTEGER (0..266),
  a267 BOOLEAN,
  a268 INTEGER (0..268),
  a269 BOOLEAN,
  a270 INTEGER (0..270),
  a271 BOOLEAN,
  a272 INTEGER (0..272),
  a273 BOOLEAN,
  a274 INTEGER (0..274),
  a275 BOOLEAN,
  a276 INTEGER (0..276),
  a277 BOOLEAN,
  a278 INTEGER (0..278),
  a279 BOOLEAN,
  a280 INTEGER (0..280),
  a281 BOOLEAN,
  a282 INTEGER (0..282),
  a283 BOOLEAN,
  a284 INTEGER (0..284),
  a285 BOOLEAN,
  a286 INTEGER (0..286),
  a287 BOOLEAN,
  a288 INTEGER (0..288),
  a289 BOOLEAN,
  a290 INTEGER (0..290),
  a291 BOOLEAN,
  a292 INTEGER (0..292),
  a293 BOOLEAN,
  a294 INTEGER (0..294),
  a295 BOOLEAN,
  a296 INTEGER (0..296),
  a297 BOOLEAN,
  a298 INTEGER (0..298),
  a299 BOOLEAN
}
C256 ::= CHOICE {
  b0 NULL,
  b1 NULL,
  b2 NULL,
  b3 NULL,
  b4 NULL,
  b5 NULL,
  b6 NULL,
  b7 NULL,
  b8 NULL,
  b9 NULL,
  b10 NULL,
  b11 NULL,
  b12 NULL,
  b13 NULL,
  b14 NULL,
  b15 NULL,
  b16 NULL,
  b17 NULL,
  b18 NULL,
  b19 NULL,
  b20 NULL,
  b21 NULL,
  b22 NULL,
  b23 NULL,
  b24 NULL,
  b25 NULL,
  b26 NULL,
  b27 NULL,
  b28 NULL,
  b29 NULL,
  b30 NULL,
  b31 NULL,
  b32 NULL,
  b33 NULL,
  b34 NULL,
  b35 NULL,
  b36 NULL,
  b37 NULL,
  b38 NULL,
  b39 NULL,
  b40 NULL,
  b41 NULL,
  b42 NULL,
  b43 NULL,
  b44 NULL,
  b45 NULL,
  b46 NULL,
  b47 NULL,
  b48 NULL,
  b49 NULL,
  b50 NULL,
  b51 NULL,
  b52 NULL,
  b53 NULL,
  b54 NULL,
  b55 NULL,
  b56 NULL,
  b57 NULL,
  b58 NULL,
  b59 NULL,
  b60 NULL,
  b61 NULL,
  b62 NULL,
  b63 NULL,
  b64 NULL,
  b65 NULL,
  b66 NULL,
  b67 NULL,
  b68 NULL,
  b69 NULL,
  b70 NULL,
  b71 NULL,
  b72 NULL,
  b73 NULL,
  b74 NULL,
  b75 NULL,
  b76 NULL,
  b77 NULL,
  b78 NULL,
  b79 NULL,
  b80 NULL,
  b81 NULL,
  b82 NULL,
  b83 NULL,
  b84 NULL,
  b85 NULL,
  b86 NULL,
  b87 NULL,
  b88 NULL,
  b89 NULL,
  b90 NULL,
  b91 NULL,
  b92 NULL,
  b93 NULL,
  b94 NULL,
  b95 NULL,
  b96 NULL,
  b97 NULL,
  b98 NULL,
  b99 NULL,
  b100 NULL,
  b101 NULL,
  b102 NULL,
  b103 NULL,
  b104 NULL,
  b105 NULL,
  b106 NULL,
  b107 NULL,
  b108 NULL,
  b109 NULL,
  b110 NULL,
  b111 NULL,
  b112 NULL,
  b113 NULL,
  b114 NULL,
  b115 NULL,
  b116 NULL,
  b117 NULL,
  b118 NULL,
  b119 NULL,
  b120 NULL,
  b121 NULL,
  b122 NULL,
  b123 NULL,
  b124 NULL,
  b125 NULL,
  b126 NULL,
  b127 NULL,
  b128 NULL,
  b129 NULL,
  b130 NULL,
  b131 NULL,
  b132 NULL,
  b133 NULL,
  b134 NULL,
  b135 NULL,
  b136 NULL,
  b137 NULL,
  b138 NULL,
  b139 NULL,
  b140 NULL,
  b141 NULL,
  b142 NULL,
  b143 NULL,
  b144 NULL,
  b145 NULL,
  b146 NULL,
  b147 NULL,
  b148 NULL,
  b149 NULL,
  b150 NULL,
  b151 NULL,
  b152 NULL,
  b153 NULL,
  b154 NULL,
  b155 NULL,
  b156 NULL,
  b157 NULL,
  b158 NULL,
  b159 NULL,
  b160 NULL,
  b161 NULL,
  b162 NULL,
  b163 NULL,
  b164 NULL,
  b165 NULL,
  b166 NULL,
  b167 NULL,
  b168 NULL,
  b169 NULL,
  b170 NULL,
  b171 NULL,
  b172 NULL,
  b173 NULL,
  b174 NULL,
  b175 NULL,
  b176 NULL,
  b177 NULL,
  b178 NULL,
  b179 NULL,
  b180 NULL,
  b181 NULL,
  b182 NULL,
  b183 NULL,
  b184 NULL,
  b185 NULL,
  b186 NULL,
  b187 NULL,
  b188 NULL,
  b189 NULL,
  b190 NULL,
  b191 NULL,
  b192 NULL,
  b193 NULL,
  b194 NULL,
  b195 NULL,
  b196 NULL,
  b197 NULL,
  b198 NULL,
  b199 NULL,
  b200 NULL,
  b201 NULL,
  b202 NULL,
  b203 NULL,
  b204 NULL,
  b205 NULL,
  b206 NULL,
  b207 NULL,
  b208 NULL,
  b209 NULL,
  b210 NULL,
  b211 NULL,
  b212 NULL,
  b213 NULL,
  b214 NULL,
  b215 NULL,
  b216 NULL,
  b217 NULL,
  b218 NULL,
  b219 NULL,
  b220 NULL,
  b221 NULL,
  b222 NULL,
  b223 NULL,
  b224 NULL,
  b225 NULL,
  b226 NULL,
  b227 NULL,
  b228 NULL,
  b229 NULL,
  b230 NULL,
  b231 NULL,
  b232 NULL,
  b233 NULL,
  b234 NULL,
  b235 NULL,
  b236 NULL,
  b237 NULL,
  b238 NULL,
  b239 NULL,
  b240 NULL,
  b241 NULL,
  b242 NULL,
  b243 NULL,
  b244 NULL,
  b245 NULL,
  b246 NULL,
  b247 NULL,
  b248 NULL,
  b249 NULL,
  b250 NULL,
  b251 NULL,
  b252 NULL,
  b253 NULL,
  b254 NULL,
  b255 NULL
}
C300x ::= CHOICE {
  a0 INTEGER (0..0),
  a1 BOOLEAN,
  a2 INTEGER (0..2),
  a3 BOOLEAN,
  a4 INTEGER (0..4),
  a5 BOOLEAN,
  a6 INTEGER (0..6),
  a7 BOOLEAN,
  a8 INTEGER (0..8),
  a9 BOOLEAN,
  a10 INTEGER (0..10),
  a11 BOOLEAN,
  a12 INTEGER (0..12),
  a13 BOOLEAN,
  a14 INTEGER (0..14),
  a15 BOOLEAN,
  a16 INTEGER (0..16),
  a17 BOOLEAN,
  a18 INTEGER (0..18),
  a19 BOOLEAN,
  a20 INTEGER (0..20),
  a21 BOOLEAN,
  a22 INTEGER (0..22),
  a23 BOOLEAN,
  a24 INTEGER (0..24),
  a25 BOOLEAN,
  a26 INTEGER (0..26),
  a27 BOOLEAN,
  a28 INTEGER (0..28),
  a29 BOOLEAN,
  a30 INTEGER (0..30),
  a31 BOOLEAN,
  a32 INTEGER (0..32),
  a33 BOOLEAN,
  a34 INTEGER (0..34),
  a35 BOOLEAN,
  a36 INTEGER (0..36),
  a37 BOOLEAN,
  a38 INTEGER (0..38),
  a39 BOOLEAN,
  a40 INTEGER (0..40),
  a41 BOOLEAN,
  a42 INTEGER (0..42),
  a43 BOOLEAN,
  a44 INTEGER (0..44),
  a45 BOOLEAN,
  a46 INTEGER (0..46),
  a47 BOOLEAN,
  a48 INTEGER (0..48),
  a49 BOOLEAN,
  a50 INTEGER (0..50),
  a51 BOOLEAN,
  a52 INTEGER (0..52),
  a53 BOOLEAN,
  a54 INTEGER (0..54),
  a55 BOOLEAN,
  a56 INTEGER (0..56),
  a57 BOOLEAN,
  a58 INTEGER (0..58),
  a59 BOOLEAN,
  a60 INTEGER (0..60),
  a61 BOOLEAN,
  a62 INTEGER (0..62),
  a63 BOOLEAN,
  a64 INTEGER (0..64),
  a65 BOOLEAN,
  a66 INTEGER (0..66),
  a67 BOOLEAN,
  a68 INTEGER (0..68),
  a69 BOOLEAN,
  a70 INTEGER (0..70),
  a71 BOOLEAN,
  a72 INTEGER (0..72),
  a73 BOOLEAN,
  a74 INTEGER (0..74),
  a75 BOOLEAN,
  a76 INTEGER (0..76),
  a77 BOOLEAN,
  a78 INTEGER (0..78),
  a79 BOOLEAN,
  a80 INTEGER (0..80),
  a81 BOOLEAN,
  a82 INTEGER (0..82),
  a83 BOOLEAN,
  a84 INTEGER (0..84),
  a85 BOOLEAN,
  a86 INTEGER (0..86),
  a87 BOOLEAN,
  a88 INTEGER (0..88),
  a89 BOOLEAN,
  a90 INTEGER (0..90),
  a91 BOOLEAN,
  a92 INTEGER (0..92),
  a93 BOOLEAN,
  a94 INTEGER (0..94),
  a95 BOOLEAN,
  a96 INTEGER (0..96),
  a97 BOOLEAN,
  a98 INTEGER (0..98),
  a99 BOOLEAN,
  a100 INTEGER (0..100),
  a101 BOOLEAN,
  a102 INTEGER (0..102),
  a103 BOOLEAN,
  a104 INTEGER (0..104),
  a105 BOOLEAN,
  a106 INTEGER (0..106),
  a107 BOOLEAN,
  a108 INTEGER (0..108),
  a109 BOOLEAN,
  a110 INTEGER (0..110),
  a111 BOOLEAN,
  a112 INTEGER (0..112),
  a113 BOOLEAN,
  a114 INTEGER (0..114),
  a115 BOOLEAN,
  a116 INTEGER (0..116),
  a117 BOOLEAN,
  a118 INTEGER (0..118),
  a119 BOOLEAN,
  a120 INTEGER (0..120),
  a121 BOOLEAN,
  a122 INTEGER (0..122),
  a123 BOOLEAN,
  a124 INTEGER (0..124),
  a125 BOOLEAN,
  a126 INTEGER (0..126),
  a127 BOOLEAN,
  a128 INTEGER (0..128),
  a129 BOOLEAN,
  a130 INTEGER (0..130),
  a131 BOOLEAN,
  a132 INTEGER (0..132),
  a133 BOOLEAN,
  a134 INTEGER (0..134),
  a135 BOOLEAN,
  a136 INTEGER (0..136),
  a137 BOOLEAN,
  a138 INTEGER (0..138),
  a139 BOOLEAN,
  a140 INTEGER (0..140),
  a141 BOOLEAN,
  a142 INTEGER (0..142),
  a143 BOOLEAN,
  a144 INTEGER (0..144),
  a145 BOOLEAN,
  a146 INTEGER (0..146),
  a147 BOOLEAN,
  a148 INTEGER (0..148),
  a149 BOOLEAN,
  a150 INTEGER (0..150),
  a151 BOOLEAN,
  a152 INTEGER (0..152),
  a153 BOOLEAN,
  a154 INTEGER (0..154),
  a155 BOOLEAN,
  a156 INTEGER (0..156),
  a157 BOOLEAN,
  a158 INTEGER (0..158),
  a159 BOOLEAN,
  a160 INTEGER (0..160),
  a161 BOOLEAN,
  a162 INTEGER (0..162),
  a163 BOOLEAN,
  a164 INTEGER (0..164),
  a165 BOOLEAN,
  a166 INTEGER (0..166),
  a167 BOOLEAN,
  a168 INTEGER (0..168),
  a169 BOOLEAN,
  a170 INTEGER (0..170),
  a171 BOOLEAN,
  a172 INTEGER (0..172),
  a173 BOOLEAN,
  a174 INTEGER (0..174),
  a175 BOOLEAN,
  a176 INTEGER (0..176),
  a177 BOOLEAN,
  a178 INTEGER (0..178),
  a179 BOOLEAN,
  a180 INTEGER (0..180),
  a181 BOOLEAN,
  a182 INTEGER (0..182),
  a183 BOOLEAN,
  a184 INTEGER (0..184),
  a185 BOOLEAN,
  a186 INTEGER (0..186),
  a187 BOOLEAN,
  a188 INTEGER (0..188),
  a189 BOOLEAN,
  a190 INTEGER (0..190),
  a191 BOOLEAN,
  a192 INTEGER (0..192),
  a193 BOOLEAN,
  a194 INTEGER (0..194),
  a195 BOOLEAN,
  a196 INTEGER (0..196),
  a197 BOOLEAN,
  a198 INTEGER (0..198),
  a199 BOOLEAN,
  a200 INTEGER (0..200),
  a201 BOOLEAN,
  a202 INTEGER (0..202),
  a203 BOOLEAN,
  a204 INTEGER (0..204),
  a205 BOOLEAN,
  a206 INTEGER (0..206),
  a207 BOOLEAN,
  a208 INTEGER (0..208),
  a209 BOOLEAN,
  a210 INTEGER (0..210),
  a211 BOOLEAN,
  a212 INTEGER (0..212),
  a213 BOOLEAN,
  a214 INTEGER (0..214),
  a215 BOOLEAN,
  a216 INTEGER (0..216),
  a217 BOOLEAN,
  a218 INTEGER (0..218),
  a219 BOOLEAN,
  a220 INTEGER (0..220),
  a221 BOOLEAN,
  a222 INTEGER (0..222),
  a223 BOOLEAN,
  a224 INTEGER (0..224),
  a225 BOOLEAN,
  a226 INTEGER (0..226),
  a227 BOOLEAN,
  a228 INTEGER (0..228),
  a229 BOOLEAN,
  a230 INTEGER (0..230),
  a231 BOOLEAN,
  a232 INTEGER (0..232),
  a233 BOOLEAN,
  a234 INTEGER (0..234),
  a235 BOOLEAN,
  a236 INTEGER (0..236),
  a237 BOOLEAN,
  a238 INTEGER (0..238),
  a239 BOOLEAN,
  a240 INTEGER (0..240),
  a241 BOOLEAN,
  a242 INTEGER (0..242),
  a243 BOOLEAN,
  a244 INTEGER (0..244),
  a245 BOOLEAN,
  a246 INTEGER (0..246),
  a247 BOOLEAN,
  a248 INTEGER (0..248),
  a249 BOOLEAN,
  a250 INTEGER (0..250),
  a251 BOOLEAN,
  a252 INTEGER (0..252),
  a253 BOOLEAN,
  a254 INTEGER (0..254),
  a255 BOOLEAN,
  a256 INTEGER (0..256),
  a257 BOOLEAN,
  a258 INTEGER (0..258),
  a259 BOOLEAN,
  a260 INTEGER (0..260),
  a261 BOOLEAN,
  a262 INTEGER (0..262),
  a263 BOOLEAN,
  a264 INTEGER (0..264),
  a265 BOOLEAN,
  a266 INTEGER (0..266),
  a267 BOOLEAN,
  a268 INTEGER (0..268),
  a269 BOOLEAN,
  a270 INTEGER (0..270),
  a271 BOOLEAN,
  a272 INTEGER (0..272),
  a273 BOOLEAN,
  a274 INTEGER (0..274),
  a275 BOOLEAN,
  a276 INTEGER (0..276),
  a277 BOOLEAN,
  a278 INTEGER (0..278),
  a279 BOOLEAN,
  a280 INTEGER (0..280),
  a281 BOOLEAN,
  a282 INTEGER (0..282),
  a283 BOOLEAN,
  a284 INTEGER (0..284),
  a285 BOOLEAN,
  a286 INTEGER (0..286),
  a287 BOOLEAN,
  a288 INTEGER (0..288),
  a289 BOOLEAN,
  a290 INTEGER (0..290),
  a291 BOOLEAN,
  a292 INTEGER (0..292),
  a293 BOOLEAN,
  a294 INTEGER (0..294),
  a295 BOOLEAN,
  a296 INTEGER (0..296),
  a297 BOOLEAN,
  a298 INTEGER (0..298),
  a299 BOOLEAN,
  ...,
  y1 BOOLEAN
}
W2 ::= SEQUENCE { flag BOOLEAN, e E300, c C256 }
END
